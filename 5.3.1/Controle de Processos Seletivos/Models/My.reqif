# Specification: Specification Document
- Description: Requirements Document

## R1 (Requirement Type)
O sistema deverá permitir o login de usuários

## R3 (Requirement Type)
O sistema deverá apresentar as principais funções na tela inicial

## R4 (Requirement Type)
O sistema deverá permitir o cadastramento de concursos

### R5 (Requirement Type)
O sistema irá solicitar o nome da empresa foco do concurso

### R6 (Requirement Type)

## R2
